module my-yang-module {
  yang-version 1.1;
  namespace "urn:ietf:params:xml:ns:yang:my-yang-module";
  prefix mym;

  leaf leaf {
    type string;
  }

  leaf-list leaf-list {
    type string;
  }

  container container {
    presence "so mandatory-leaf doesn't make mandatory-container";
    leaf mandatory-leaf {
      type string;
      mandatory true;
    }
  }

  list list {
    key key;
    leaf key {
      type string;
    }
    leaf val {
      type string;
    }
  }

  anydata anydata;

}
