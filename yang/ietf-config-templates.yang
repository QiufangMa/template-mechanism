module ietf-config-templates {
  yang-version 1.1;
  namespace "urn:ietf:params:xml:ns:yang:ietf-config-templates";
  prefix yct;

  import ietf-yang-types {
    prefix yang;
    reference
      "RFC 6991: Common YANG Data Types";
  }

  organization
    "IETF NETMOD (Network Modeling) Working Group";
  contact
    "WG Web:  https://datatracker.ietf.org/wg/netmod/
     WG List: NETMOD <mailto:netmod@ietf.org>
     
     Editor: Kent Watsen
             <mailto:kent+ietf@watsen.net>
     Editor: Qiufang Ma
             <mailto:maqiufang1@huawei.com>
     Editor: Deepak Rajaram
             <mailto:deepak.rajaram@nokia.com>";
             
  description
    "This module defines a top-level 'templates' node, and an
     'apply-templates' grouping.

     Copyright (c) 2026 IETF Trust and the persons identified
     as authors of the code. All rights reserved.

     Redistribution and use in source and binary forms, with
     or without modification, is permitted pursuant to, and
     subject to the license terms contained in, the Revised
     BSD License set forth in Section 4.c of the IETF Trust's
     Legal Provisions Relating to IETF Documents
     (https://trustee.ietf.org/license-info).

     This version of this YANG module is part of RFC XXXX
     (https://www.rfc-editor.org/info/rfcXXXX); see the RFC
     itself for full legal notices.

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.";

   revision 2026-07-03 {
     description
       "Initial revision.";
     reference
       "RFC XXXX: YANG Templates";
   }

   list templates {
     key name;
     description
       "The list of templates managed on this device.";
     leaf name {
       type string;
       description
         "The name of the template.";
     }
     leaf description {
       type string;
       description
         "A textual description of the template.";
     }
     leaf data-path {
       type yang:xpath1.0; // FIXME: should be YPath?
       default "/";
       description
         "The path location in the server's data tree that the
         ../content node is an instance of.  The data-path MUST
         not begin with '/ietf-config-template:templates'.";
     }
     anydata content {
       mandatory true;
       description
         "A subset of server configuration beginning at the
          location identified by the ../data-path node.  All
          top-level nodes MUST be namespace qualified.  When
          ../data-path is '/', the content MUST NOT define
          any nodes under '/ietf-config-template:templates'.";
     }
   }

   grouping apply-templates {
     description
       "A grouping that is conceptually used (i.e., the 'uses'
        statement) at every 'container' and 'list' node in the
        configuration.";
     leaf-list apply-templates {
       type leafref {
         path /yct:templates/yct:name;
       }
       ordered-by user;
       description
         "A user-ordered list of template references.";
     }
   }


   // FIXME: augment "with-templates-expanded" into NETCONF RPCs, what about RESTCONF?


}
